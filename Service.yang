module example-service {
  namespace "http://qubuhub.org/service";
  prefix svc;

  container service {
    leaf name {
      type string;
    }

    leaf enabled {
      type boolean;
      default true;
    }
  }
}
